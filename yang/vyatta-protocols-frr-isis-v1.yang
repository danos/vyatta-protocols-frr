module vyatta-protocols-frr-isis-v1 {
  namespace "urn:vyatta.com:mgmt:vyatta-protocols-frr-isis:1";
  prefix vyatta-protocols-frr-isis-v1;

  import vyatta-protocols-v1 {
    prefix protocols;
  }
  import vyatta-types-v1 {
    prefix types;
  }
  import configd-v1 {
    prefix configd;
  }
  import vyatta-interfaces-v1 {
    prefix if;
  }
  import vyatta-interfaces-dataplane-v1 {
    prefix interfaces-dataplane;
  }
  import vyatta-interfaces-loopback-v1 {
    prefix interfaces-loopback;
  }
  import vyatta-interfaces-switch-v1 {
    prefix interfaces-switch;
  }

  organization "Niral Networks Private Limited";
  contact
    "Niral Networks
    Postal: Sigma Soft Tech Park, Whitefield Main Road,
    Bengaluru, India 560066
    Web: www.niralnetworks.com";

  description
    "Copyright (c) 2019-2020, Niral Networks Intellectual Property.
    All rights reserved.

    Redistribution and use in source and binary forms, with or
    without modification, are permitted provided that the following
    conditions are met:

    1. Redistributions of source code must retain the above copyright
    notice, this list of conditions and the following disclaimer.
    2. Redistributions in binary form must reproduce the above
    copyright notice, this list of conditions and the following
    disclaimer in the documentation and/or other materials provided
    with the distribution.
    3. Neither the name of the copyright holder nor the names of its
    contributors may be used to endorse or promote products derived
    from this software without specific prior written permission.

    THIS SOFTWARE IS PROVIDED BY THE COPYRIGHT HOLDERS AND CONTRIBUTORS
    'AS IS' AND ANY EXPRESS OR IMPLIED WARRANTIES, INCLUDING, BUT NOT
    LIMITED TO, THE IMPLIED WARRANTIES OF MERCHANTABILITY AND FITNESS
    FOR A PARTICULAR PURPOSE ARE DISCLAIMED. IN NO EVENT SHALL THE
    COPYRIGHT HOLDER OR CONTRIBUTORS BE LIABLE FOR ANY DIRECT, INDIRECT,
    INCIDENTAL, SPECIAL, EXEMPLARY, OR CONSEQUENTIAL DAMAGES (INCLUDING,
    BUT NOT LIMITED TO, PROCUREMENT OF SUBSTITUTE GOODS OR SERVICES;
    LOSS OF USE, DATA, OR PROFITS; OR BUSINESS INTERRUPTION) HOWEVER
    CAUSED AND ON ANY THEORY OF LIABILITY, WHETHER IN CONTRACT, STRICT
    LIABILITY, OR TORT (INCLUDING NEGLIGENCE OR OTHERWISE) ARISING IN
    ANY WAY OUT OF THE USE OF THIS SOFTWARE, EVEN IF ADVISED OF THE
    POSSIBILITY OF SUCH DAMAGE.

    SPDX-License-Identifier: BSD-3-Clause
    The YANG module package for vyatta-protocols-frr-isis-v1";

  revision 2020-12-18 {
    description 
      "Add IPv6 ISIS interface config option.
      Added ISIS topology and mpls-te configuration.
      Added ISIS under vif interface";
  }

  revision 2020-10-10 {
    description "Added ISIS under loopback interface";
  }

  revision 2020-03-30 {
    description "Initial revision of version 1";
  }

  typedef level {
    type enumeration {
      enum "level-1" {
        value 1;
        configd:help "This enum indicates L1-only capability.";
        description "This enum indicates L1-only capability.";
      }
      enum "level-2-only" {
        value 2;
        configd:help "This enum indicates L2-only capability.";
        description "This enum indicates L2-only capability.";
      }
      enum "level-1-2" {
        value 3;
        configd:help "This enum indicates capability for both levels.";
        description "This enum indicates capability for both levels.";
      }
    }
    configd:help "This type defines IS-IS level of an object.";
    description "This type defines IS-IS level of an object.";
  }

  typedef isis-level {
    type enumeration {
      enum "level-1" {
        value 1;
        configd:help "This enum indicates L1-only capability.";
        description "This enum indicates L1-only capability.";
      }
      enum "level-2" {
        value 2;
        configd:help "This enum indicates L2-only capability.";
        description "This enum indicates L2-only capability.";
      }
    }
    configd:help "This type defines IS-IS level of an object.";
    description "This type defines IS-IS level of an object.";
  }

  typedef network-type {
    type enumeration {
      enum "point-to-point" {
        value 0;
        configd:help "Point-to-point circuit network-type.";
        description "Point-to-point circuit network-type.";
      }
    }
  }

  typedef snpa {
    type string {
      length "0 .. 20";
    }
    configd:help "This type defines the Subnetwork Point of Attachment (SNPA) format.
    The SNPA should be encoded according to the rules specified for the particular type
    of subnetwork being used. As an example, for an ethernet subnetwork, the SNPA is
    encoded as a MAC address like '00aa.bbcc.ddee'.";

    description "This type defines the Subnetwork Point of Attachment (SNPA) format.
    The SNPA should be encoded according to the rules specified for the particular type
    of subnetwork being used. As an example, for an ethernet subnetwork, the SNPA is
    encoded as a MAC address like '00aa.bbcc.ddee'.";
  }

  typedef net-address {
    type string {
      pattern "[a-fA-F0-9]{2}(\\.[a-fA-F0-9]{4}){3,9}\\.[a-fA-F0-9]{2}";
    }
    configd:help "This type defines an OSI NET address using a pattern,
    An example net-address is 49.0123.6452.1972.00";
    description "This type defines an OSI NET address using a pattern,
    An example net-address is 49.0123.6452.1972.00";
  }

  typedef metric-style-type {
    type enumeration {
      enum "narrow" {
        value 0;
        configd:help "This enum describes narrow metric style";
        description "This enum describes narrow metric style";
        reference "RFC1195";
      }
      enum "wide" {
        value 1;
        configd:help "This enum describes wide metric style";
        description "This enum describes wide metric style";
        reference "RFC5305";
      }
      enum "transition" {
        value 2;
        configd:help "This enum describes transition metric style";
        description "This enum describes transition metric style";
      }
    }
  }

  typedef timer-val {
    type uint16 {
      range "0..60000";
    }
  }

  grouping isis-password {
    leaf clear {
      configd:help "Clear-text authentication type.";
      description "Clear-text authentication type.";
      type string {
        length "1..254";
      }
      configd:secret "true";
      must "not(../md5)" {
        error-message "Can't configure both clear and md5 for password";
      }
    }
    leaf md5 {
      configd:help "MD5 authentication type.";
      description "MD5 authentication type.";
      type string {
        length "1..254";
      }
      configd:secret "true";
    }
  }

  grouping isis-area-domain-password {
    container area-password {
      description "area password.";
      configd:help "area password.";
      uses isis-password;
    }
    container domain-password {
      description "domain password.";
      configd:help "domain password.";
      uses isis-password;
    }
  }

  grouping isis-net {
    leaf net {
      type net-address;
      configd:pattern-help "<XX.XXXX. ... .XXX.XX>";
      configd:help "XX.XXXX. ... .XXX.XX  Network entity title (NET)";
      description "XX.XXXX. ... .XXX.XX  Network entity title (NET)";
    }
    container default-information {
      configd:help "Distribution of default information.";
      description "Distribution of default information.";
      container originate {
        configd:help "Distribute a default route.";
        description "Distribute a default route.";
        list ipv4 {
          key "level";
          configd:help "Distribute default route for IPv4.";
          description "Distribute default route for IPv4.";
          leaf level {
            type isis-level;
          }
        }

        list ipv6 {
          key "level";
          configd:help "Distribute default route for IPv6.";
          description "Distribute default route for IPv6.";
          leaf level {
            type isis-level;
          }
        }
      }
    }
    leaf log-adjacency-changes {
      type empty;
      configd:help "Log changes to the IS-IS adjacencies in this area.";
      description "Log changes to the IS-IS adjacencies in this area.";
    }
    container lsp-gen-interval {
      configd:help "Minimum LSP regeneration interval.";
      description "Minimum LSP regeneration interval.";
      leaf level-1 {
        type uint16 {
          range "1..120";
        }
        units "seconds";
        configd:help "Minimum time allowed before level-1 LSP retransmissions.";
        description "Minimum time allowed before level-1 LSP retransmissions.";
      }
      leaf level-2 {
        type uint16 {
          range "1..120";
        }
        units "seconds";
        configd:help "Minimum time allowed before level-2 LSP retransmissions.";
        description "Minimum time allowed before level-2 LSP retransmissions.";
      }
    }
    container lsp-refresh-interval {
      description "LSP refresh interval";
      configd:help "LSP refresh interval";
      leaf level-1 {
        type uint16 {
          range "1..65535";
        }
        units "seconds";
        configd:help "LSP refresh interval for level-1.";
        description "LSP refresh interval for level-1.";
        must ". > ../../lsp-gen-interval/level-1" {
          error-message "lsp refresh interval must be greater than lsp general interval";
        }
      }
      leaf level-2 {
        type uint16 {
          range "1..65535";
        }
        units "seconds";
        configd:help "LSP refresh interval for level-2.";
        description "LSP refresh interval for level-2.";
        must ". > ../../lsp-gen-interval/level-2" {
          error-message "lsp refresh interval must be greater than lsp general interval";
        }
      }
    }

    container max-lsp-lifetime {
      configd:help "Maximum LSP lifetime.";
      description "Maximum LSP lifetime.";
      leaf level-1 {
        type uint16 {
          range "350..65535";
        }
        units "seconds";
        configd:help "Maximum LSP lifetime for level-1.";
        description "Maximum LSP lifetime for level-1.";
      }
      leaf level-2 {
        type uint16 {
          range "350..65535";
        }
        units "seconds";
        configd:help "Maximum LSP lifetime for level-2.";
        description "Maximum LSP lifetime for level-2.";
      }
    }

    leaf set-overload-bit {
      type empty;
      configd:help "If true, avoid any transit traffic.";
      description "If true, avoid any transit traffic.";
    }

    container spf-delay-ietf {
      presence "Present if IETF SPF back-off delay is enabled.";
      configd:help "IETF SPF delay algorithm.";
      description "IETF SPF delay algorithm.";
      leaf init-delay {
        configd:help "Delay used while in QUIET state";
        description "Delay used while in QUIET state";
        default 500;
        type timer-val;
        units "msec";
      }
      leaf short-delay {
        configd:help "Delay used while in SHORT_WAIT state";
        description "Delay used while in SHORT_WAIT state";
        default 500;
        type timer-val;
        units "msec";
      }
      leaf long-delay {
        configd:help "Delay used while in LONG_WAIT state";
        description "Delay used while in LONG_WAIT state";
        default 500;
        type timer-val;
        units "msec";
      }
      leaf holddown {
        configd:help "Time with no received IGP events before considering IGP stable";
        description "Time with no received IGP events before considering IGP stable";
        default 500;
        type timer-val;
        units "msec";
      }
      leaf time-to-learn {
        configd:help "Max duration needed to learn all the events related to a single failure";
        description "Max duration needed to learn all the events related to a single failure";
        default 500;
        type timer-val;
        units "msec";
      }
    }

    container spf-interval {
      configd:help "Minimum interval between SPF calculations";
      description "Minimum interval between SPF calculations";
      leaf level-1 {
        type uint16 {
          range "1..120";
        }
        units "seconds";
        configd:help "Minimum time between consecutive level-1 SPFs.";
        description "Minimum time between consecutive level-1 SPFs.";
      }
      leaf level-2 {
        type uint16 {
          range "1..120";
        }
        units "seconds";
        configd:help "Minimum time between consecutive level-2 SPFs.";
        description "Minimum time between consecutive level-2 SPFs.";
      }
    }

    leaf is-type {
      type level;
      configd:help "IS Level for this routing process (OSI only)";
    }

    leaf metric-style {
      type metric-style-type;
      description "Define the style of TLVs metric supported.";
      configd:help "Define the style of TLVs metric supported.";
    }

    leaf lsp-mtu {
      type uint16 {
        range "128..4352";
      }
      configd:help "MTU of an LSP.";
      description "MTU of an LSP.";
    }

    container mpls-te {
      presence "Enable MPLS-TE";
      configd:help "MPLS-TE specific commands.";
      leaf router-address {
        type types:ipv4-address;
        configd:help "Stable IP address of the advertising router.";
        description "Stable IP address of the advertising router.";
      }
    }

    container topology {
      configd:help "Configure IS-IS topologies.";
      description "Configure IS-IS topologies.";
      container ipv4-multicast {
        presence "IPv4-multicast topology is configured for this area.";
        description "IPv4 multicast topology.";
        configd:help "IPv4 multicast topology.";
        leaf overload {
          type empty;
          configd:help "Set overload bit for topology.";
        }
      }

      container ipv4-unicast {
        presence "IPv4-unicast topology is configured for this area.";
        description "IPv4 unicast topology.";
        configd:help "IPv4 unicast topology.";
        leaf overload {
          type empty;
          configd:help "Set overload bit for topology.";
        }
      }

      container ipv4-mgmt {
        presence "IPv4-management topology is configured for this area.";
        description "IPv4 management topology.";
        configd:help "IPv4 management topology.";
        leaf overload {
          type empty;
          configd:help "Set overload bit for topology.";
        }
      }

      container ipv6-unicast {
        presence "IPv6-unicast topology is configured for this area.";
        description "IPv6 unicast topology.";
        configd:help "IPv6 unicast topology.";
        leaf overload {
          type empty;
          configd:help "Set overload bit for topology.";
        }
      }

      container ipv6-multicast {
        presence "IPv6-multicast topology is configured for this area.";
        description "IPv6 multicast topology.";
        configd:help "IPv6 multicast topology.";
        leaf overload {
          type empty;
          configd:help "Set overload bit for topology.";
        }
      }

      container ipv6-mgmt {
        presence "IPv6-management topology is configured for this area.";
        description "IPv6 management topology.";
        configd:help "IPv6 management topology.";
        leaf overload {
          type empty;
          configd:help "Set overload bit for topology.";
        }
      }

      container ipv6-dstsrc {
        presence "IPv6 destination-source topology is configured for this area.";
        description "IPv6 destination-source topology.";
        configd:help "IPv6 destination-source topology.";
        leaf overload {
          type empty;
          configd:help "Set overload bit for topology.";
        }
      }
    }
  }

  grouping redistribute-protocol {
    leaf kernel {
      type isis-level;
      configd:help "Kernel routes (not installed via the zebra RIB).";
      description "Kernel routes (not installed via the zebra RIB).";
    }
    leaf connected {
      type isis-level;
      configd:help "Connected routes (directly attached subnet or host).";
      description "Connected routes (directly attached subnet or host).";
    }
    leaf static {
      type isis-level;
      configd:help "Statically configured routes.";
      description "Statically configured routes.";
    }
    leaf ospf {
      type isis-level;
      configd:help "Open Shortest Path First (OSPFv2).";
      description "Open Shortest Path First (OSPFv2).";
    }
    leaf bgp {
      type isis-level;
      configd:help "Redistribute bgp routes";
      description "Redistribute bgp routes";
    }
    leaf rip {
      type isis-level;
      configd:help "Redistribute rip routes";
      description "Redistribute rip routes";
    }
  }

  grouping isis-redistribute {
    container redistribute {
      configd:help "Redistributes routes learned from other routing protocols.";
      description "Redistributes routes learned from other routing protocols.";
      container ipv4 {
        configd:help "IPv4 route redistribution.";
        description "IPv4 route redistribution.";
        uses redistribute-protocol;
      }
      container ipv6 {
        configd:help "IPv6 route redistribution.";
        description "IPv6 route redistribution.";
        uses redistribute-protocol;
      }
    }
  }

  augment /protocols:protocols {
    list isis {
      configd:help "Intermediate System to Intermediate System (ISIS) parameters";
      description "Intermediate System to Intermediate System (ISIS) parameters";

      key "area-tag";
      leaf area-tag {
        configd:help "Area-tag associated to this routing instance";
        description "Area-tag associated to this routing instance";
        type string;
      }
      uses isis-redistribute;
      uses isis-net;
      uses isis-area-domain-password;
    }
  }

  grouping itf-ip-router-isis {
    container isis {
      configd:help "IS-IS routing protocol";
      leaf instance {
        type string;
          configd:help "Extended isis-id of the ISIS instance";
          description "Extended isis-id of the ISIS instance";
      }
    }
  }

  grouping isis {
    container isis {
      configd:help "IS-IS routing protocol";
      leaf circuit-type {
        type level;
        configd:help "IS-type of this circuit.";
        description "IS-type of this circuit.";
      }
      container hello-interval {
        configd:help "Interval between consecutive hello messages.";
        description "Interval between consecutive hello messages.";
        leaf level-1 {
          type uint32 {
            range "1..600";
          }
          units "seconds";
          configd:help "Holding time for level-1; interval will depend on multiplier.";
          description "Holding time for level-1; interval will depend on multiplier.";
        }
        leaf level-2 {
          type uint32 {
            range "1..600";
          }
          units "seconds";
          configd:help "Holding time for level-2; interval will depend on multiplier.";
          description "Holding time for level-2; interval will depend on multiplier.";
        }
      }
      container metric {
        configd:help "Metric for this IS-IS circuit.";
        description "Metric for this IS-IS circuit.";
        leaf level-1 {
          type uint32 {
            range "0..16777215";
          }
          configd:help "Level-1 metric for this IS-IS circuit.";
          description "Level-1 metric for this IS-IS circuit.";
        }
        leaf level-2 {
          type uint32 {
            range "0..16777215";
          }
          configd:help "Level-2 metric for this IS-IS circuit.";
          description "Level-2 metric for this IS-IS circuit.";
        }
      }

      container priority {
        configd:help "Priority for Designated Router election.";
        description "Priority for Designated Router election.";
        leaf level-1 {
          type uint8 {
            range "0..127";
          }
          configd:help "Level-1 priority for this IS-IS circuit.";
          description "Level-1 priority for this IS-IS circuit.";
        }
        leaf level-2 {
          type uint8 {
            range "0..127";
          }
          configd:help "Level-2 priority for this IS-IS circuit.";
          description "Level-2 priority for this IS-IS circuit.";
        }
      }

      leaf passive {
        type empty;
        configd:help "Interface is in passive mode.";
        description "Interface is in passive mode.";
      }

      container password {
        presence "Present if a password is set for this IS interface.";
        configd:help "Authentication password for an IS-IS area.";
        description "Authentication password for an IS-IS area.";
        uses isis-password;
      }

      leaf network {
        type network-type;
        must "(. = 'point-to-point') or (. = 'broadcast')";
        configd:help "Explicitly configured type of IS-IS circuit (broadcast or point-to-point).";
        description "Explicitly configured type of IS-IS circuit (broadcast or point-to-point).";
      }
      container topology {
        configd:help "Configure IS-IS topologies.";
        leaf ipv4-unicast {
          type empty;
          description
            "IPv4 unicast topology.";
          configd:help "IPv4 unicast topology.";
        }

        leaf ipv4-multicast {
          type empty;
          description "IPv4 multicast topology.";
          configd:help "IPv4 multicast topology.";
        }

        leaf ipv4-mgmt {
          type empty;
          description
            "IPv4 management topology.";
          configd:help "IPv4 management topology.";
        }

        leaf ipv6-unicast {
          type empty;
          description
            "IPv6 unicast topology.";
          configd:help "IPv6 unicast topology.";
        }

        leaf ipv6-multicast {
          type empty;
          description
            "IPv6 multicast topology.";
          configd:help "IPv6 multicast topology.";
        }

        leaf ipv6-mgmt {
          type empty;
          description
            "IPv6 management topology.";
          configd:help "IPv6 management topology.";
        }

        leaf ipv6-dstsrc {
          type empty;
          description
            "IPv6 destination-source topology.";
          configd:help "IPv6 destination-source topology.";
        }
      }
    }
  }

  augment /if:interfaces/interfaces-dataplane:dataplane {
    uses isis;
  }
  augment /if:interfaces/interfaces-dataplane:dataplane/interfaces-dataplane:ip {
    uses itf-ip-router-isis;
  }
  augment /if:interfaces/interfaces-dataplane:dataplane/interfaces-dataplane:vif/interfaces-dataplane:ip {
    uses itf-ip-router-isis;
  }
  augment /if:interfaces/interfaces-dataplane:dataplane/interfaces-dataplane:ipv6 {
    uses itf-ip-router-isis;
  }
  augment /if:interfaces/interfaces-dataplane:dataplane/interfaces-dataplane:vif/interfaces-dataplane:ipv6 {
    uses itf-ip-router-isis;
  }
  augment /if:interfaces/interfaces-loopback:loopback {
   uses isis;
  }
  augment /if:interfaces/interfaces-loopback:loopback/interfaces-loopback:ip {
    uses itf-ip-router-isis;
  }
  augment /if:interfaces/interfaces-loopback:loopback/interfaces-loopback:ipv6 {
    uses itf-ip-router-isis;
  }
  augment /if:interfaces/interfaces-switch:switch/interfaces-switch:vif {
    uses isis;
  }
  augment /if:interfaces/interfaces-switch:switch/interfaces-switch:vif/interfaces-switch:ip {
    uses itf-ip-router-isis;
  }
  augment /if:interfaces/interfaces-switch:switch/interfaces-switch:vif/interfaces-switch:ipv6 {
    uses itf-ip-router-isis;
  }
}
