module vyatta-protocols-frr-ospf-routing-instance-v1 {
	namespace "urn:vyatta.com:mgmt:vyatta-protocols-frr-ospf-routing-instance:1";
	prefix vyatta-protocols-frr-ospf-routing-instance-v1;

	import vyatta-protocols-v1 {
		prefix protocols;
	}
	import configd-v1 {
		prefix configd;
	}
	import vyatta-routing-v1 {
		prefix routing-instance;
	}
	import vyatta-protocols-interface-validation-routing-instance-v1 {
		prefix if-validation-routing-inst;
	}
	import vyatta-protocols-frr-ospf-v1 {
		prefix ospf;
	}

	organization "AT&T, Inc.";
	contact
		"AT&T
		Postal: 208 S. Akard Street
		        Dallas, TX 75202
		Web: www.att.com";

	description
		"Copyright (c) 2018-2020, AT&T Intellectual Property.
		 All rights reserved.

		 Redistribution and use in source and binary forms, with or
		 without modification, are permitted provided that the following
		 conditions are met:

		 1. Redistributions of source code must retain the above copyright
			notice, this list of conditions and the following disclaimer.
		 2. Redistributions in binary form must reproduce the above
			copyright notice, this list of conditions and the following
			disclaimer in the documentation and/or other materials provided
			with the distribution.
		 3. Neither the name of the copyright holder nor the names of its
			contributors may be used to endorse or promote products derived
			from this software without specific prior written permission.

		 THIS SOFTWARE IS PROVIDED BY THE COPYRIGHT HOLDERS AND CONTRIBUTORS
		 'AS IS' AND ANY EXPRESS OR IMPLIED WARRANTIES, INCLUDING, BUT NOT
		 LIMITED TO, THE IMPLIED WARRANTIES OF MERCHANTABILITY AND FITNESS
		 FOR A PARTICULAR PURPOSE ARE DISCLAIMED. IN NO EVENT SHALL THE
		 COPYRIGHT HOLDER OR CONTRIBUTORS BE LIABLE FOR ANY DIRECT, INDIRECT,
		 INCIDENTAL, SPECIAL, EXEMPLARY, OR CONSEQUENTIAL DAMAGES (INCLUDING,
		 BUT NOT LIMITED TO, PROCUREMENT OF SUBSTITUTE GOODS OR SERVICES;
		 LOSS OF USE, DATA, OR PROFITS; OR BUSINESS INTERRUPTION) HOWEVER
		 CAUSED AND ON ANY THEORY OF LIABILITY, WHETHER IN CONTRACT, STRICT
		 LIABILITY, OR TORT (INCLUDING NEGLIGENCE OR OTHERWISE) ARISING IN
		 ANY WAY OUT OF THE USE OF THIS SOFTWARE, EVEN IF ADVISED OF THE
		 POSSIBILITY OF SUCH DAMAGE.

		 SPDX-License-Identifier: BSD-3-Clause

		 The YANG module package for vyatta-protocols-ospf-routing-instance-v1";

	revision 2018-11-08 {
		description "Initial revision of version 1";
	}

	augment /routing-instance:routing/routing-instance:routing-instance/routing-instance:protocols {
		container ospf {
			presence "OSPFv2 is enabled in a routing instance";
			description "OSPFv2 support for VRF";
			configd:help "OSPFv2 support for VRF";
			uses ospf:ospf-parameters {
				refine parameters/router-id {
					must "count(/protocols:protocols/ospf:ospf/ospf:parameters[ospf:router-id = current()] | " +
						"/routing-instance:routing/routing-instance:routing-instance/routing-instance:protocols/ospf/parameters[router-id = current()]) <= 1" {
							error-message "Router-id is used by another process in router";
					}
				}
			}
			uses ospf:ospf-parameters-all;
			uses if-validation-routing-inst:ospf-passive-intf-routing-inst {
				refine passive-interface {
					must 'not(starts-with(current(), "ers"))' {
						error-message "Can't configure passive-interface on erspan interfaces";
					}
					configd:help "Suppress routing updates on an interface";
					description "Suppress routing updates on an interface";
					configd:allowed "/opt/vyatta/sbin/vyatta-interfaces.pl --show all --filter-out ^ers";
				}
			}
		}
	}
}
