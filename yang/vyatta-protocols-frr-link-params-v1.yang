module vyatta-protocols-frr-link-params-v1 {
	namespace "urn:vyatta.com:mgmt:vyatta-protocols-frr-link-params:1";
	prefix vyatta-protocols-frr-link-params-v1;

	import vyatta-types-v1 {
		prefix types;
	}
	import configd-v1 {
		prefix configd;
	}
	import vyatta-interfaces-v1 {
		prefix if;
	}
	import vyatta-interfaces-dataplane-v1 {
		prefix interfaces-dataplane;
	}
	import vyatta-interfaces-loopback-v1 {
		prefix interfaces-loopback;
	}
	import vyatta-interfaces-switch-v1 {
		prefix interfaces-switch;
	}

	organization "Niral Networks Private Limited";
	contact
		"Niral Networks
		Postal: Sigma Soft Tech Park, Whitefield Main Road,
		Bengaluru, India 560066
		Web: www.niralnetworks.com";

	description
		"Copyright (c) 2019-2021, Niral Networks Intellectual Property.
		All rights reserved.

		Redistribution and use in source and binary forms, with or
		without modification, are permitted provided that the following
		conditions are met:

		1. Redistributions of source code must retain the above copyright
		notice, this list of conditions and the following disclaimer.
		2. Redistributions in binary form must reproduce the above
		copyright notice, this list of conditions and the following
		disclaimer in the documentation and/or other materials provided
		with the distribution.
		3. Neither the name of the copyright holder nor the names of its
		contributors may be used to endorse or promote products derived
		from this software without specific prior written permission.

		THIS SOFTWARE IS PROVIDED BY THE COPYRIGHT HOLDERS AND CONTRIBUTORS
		'AS IS' AND ANY EXPRESS OR IMPLIED WARRANTIES, INCLUDING, BUT NOT
		LIMITED TO, THE IMPLIED WARRANTIES OF MERCHANTABILITY AND FITNESS
		FOR A PARTICULAR PURPOSE ARE DISCLAIMED. IN NO EVENT SHALL THE
		COPYRIGHT HOLDER OR CONTRIBUTORS BE LIABLE FOR ANY DIRECT, INDIRECT,
		INCIDENTAL, SPECIAL, EXEMPLARY, OR CONSEQUENTIAL DAMAGES (INCLUDING,
		BUT NOT LIMITED TO, PROCUREMENT OF SUBSTITUTE GOODS OR SERVICES;
		LOSS OF USE, DATA, OR PROFITS; OR BUSINESS INTERRUPTION) HOWEVER
		CAUSED AND ON ANY THEORY OF LIABILITY, WHETHER IN CONTRACT, STRICT
		LIABILITY, OR TORT (INCLUDING NEGLIGENCE OR OTHERWISE) ARISING IN
		ANY WAY OUT OF THE USE OF THIS SOFTWARE, EVEN IF ADVISED OF THE
		POSSIBILITY OF SUCH DAMAGE.

		SPDX-License-Identifier: BSD-3-Clause
		The YANG module package for vyatta-protocols-frr-link-params-v1";

	revision 2021-03-02 {
		description 
			"Initial revision";
	}
	
	grouping link-params {
		container link-params {
			configd:help "Configure interface link parameters";
			leaf admin-group {
				type string {
					pattern "0[Xx][a-fA-F0-9]+";
				}
				configd:help "Administrative group membership";
				description "Administrative group membership";
			}
			leaf available-bandwidth {
				type uint64;
				units "Bytes/second";
				configd:help "Unidirectional Available Bandwidth (Bytes/second)";
				description
					"Unidirectional Available Bandwidth. This field carries the available bandwidth on a
					link, forwarding adjacency, or bundled link. For a link or forwarding adjacency, available
					bandwidth is defined to be residual bandwidth minus the measured bandwidth used for the actual
					forwarding of non-RSVP-TE LSP packets.  For a bundled link, available bandwidth is defined to be
					the sum of the component link available bandwidths minus the measured bandwidth used for the actual
					forwarding of non-RSVP-TE Label Switched Paths packets [draft-ietf-isis-te-metrics-extension-03].";
				must "../max-bandwidth" {
					error-message "Maximum Bandwidth must be set";
				}
				must "../available-bandwidth <= ../max-bandwidth" {
					error-message "Available Bandwidth cannot be greater than Maximum Bandwidth";
				}
			}
			leaf delay {
				type uint32 {
					range "0..16777215";
				}
				units "micro-second";
				configd:help "Unidirectional Average Link Delay (micro-second)";
				description "Unidirectional Average Link Delay";
			}
			leaf delay-variation {
				type uint32 {
					range "0..16777215";
				}
				units "micro-second";
				configd:help "Unidirectional Link Delay Variation (micro-second)";
				description "Unidirectional Link Delay Variation";
			}
			leaf max-bandwidth {
				type uint64;
				units "Bytes/second";
				configd:help "Maximum bandwidth that can be used (Bytes/second)";
				description "Maximum bandwidth that can be used";
			}
			leaf max-reserved-bandwidth {
				type uint64;
				units "Bytes/second";
				configd:help "Maximum bandwidth that may be reserved (Bytes/second)";
				description
					"Maximum bandwidth that may be reserved. It is the bandwidth that can
					theoretically be reserved";
				must "../max-bandwidth" {
					error-message "Maximum Bandwidth must be set";
				}
				must "../max-reserved-bandwidth <= ../max-bandwidth" {
					error-message "Maximum Reservable Bandwidth cannot be greater than Maximum Bandwidth";
				}
			}
			leaf mpls-te-metric {
				type uint32 {
					range "1..max";
				}
				configd:help "Link metric for MPLS-TE purpose";
				description "Link metric for MPLS-TE purpose";
			}
			leaf neighbor {
				type types:ipv4-address;
				configd:help "Configure remote ASBR information (Neighbor IP address and AS number)";
				description "Configure remote ASBR information (Neighbor IP address and AS number)";
			}
			leaf packet-loss {
				type uint32 {
					range 0..100;
				}
				units "Percentage";
				configd:help "Unidirectional Link Packet Loss (Percentage)";
				description "Unidirectional Link Packet Loss (Percentage)";
			}
			leaf residual-bandwidth {
				type uint64;
				units "Bytes/second";
				configd:help "Unidirectional Residual Bandwidth (Bytes/second)";
				description
					"Unidirectional Residual Bandwidth. For a link or forwarding adjacency, residual
					bandwidth is defined to be Maximum Bandwidth [RFC3630] minus the bandwidth currently allocated
					to RSVP-TE LSPs. For a bundled link, residual bandwidth is defined to be the sum of the
					component link residual bandwidths [draft-ietf-isis-te-metrics-extension-03.txt].";
				must "../max-bandwidth" {
					error-message "Maximum Bandwidth must be set";
				}
				must "../residual-bandwidth <= ../max-bandwidth" {
					error-message "Residual Bandwidth cannot be greater than Maximum Bandwidth";
				}
			}
			container unreserved-bandwidth {
				configd:help "Unreserved bandwidth at each priority level";
				description
					"Unreserved bandwidth at each priority level. Unreserved Bandwidth [RFC3630], is
					subtracted from the Maximum Reservable Bandwidth (the bandwidth that can theoretically
					be reserved) [RFC3630] and provides per-QoS-class [draft-ietf-isis-te-metrics-extension-03]";
				list priority {
					configd:help "Priority";
					description "8 sets of priority levels";
					key "tagnode";
					leaf tagnode {
						type uint32 {
							range "0..7";
						}
						configd:help "Priority";
						description "8 sets of priority levels";
					}
					leaf bandwidth {
						type uint64;
						units "Bytes/second";
						configd:help "Bandwidth (Bytes/second)";
						description "Bandwidth (Bytes/second) for each priority levels";
						must "../../../max-bandwidth" {
							error-message "Maximum Bandwidth must be set";
						}
						must "../bandwidth <= ../../../max-bandwidth" {
							error-message "Unreserved Bandwidth cannot be greater than Maximum Bandwidth";
						}
					}
				}
			}
			leaf utilised-bandwidth {
				type uint64;
				units "Bytes/second";
				configd:help "Unidirectional Utilised Bandwidth (Bytes/second)";
				description
					"Unidirectional Utilised Bandwidth. This field carries the bandwidth utilization
					on a link, forwarding adjacency, or bundled link. For a link or forwarding adjacency, bandwidth
					utilization represent the actual utilization of the link (i.e.: as measured in the router). For a
					bundled link, bandwidth utilization is defined to be the sum of the component link bandwidth utilization
					[draft-ietf-isis-te-metrics-extension-03.txt].";
				must "../max-bandwidth" {
					error-message "Maximum Bandwidth must be set";
				}
				must "../utilised-bandwidth <= ../max-bandwidth" {
					error-message "Utilised Bandwidth cannot be greater than Maximum Bandwidth";
				}

			}
		}
	}

	augment /if:interfaces/interfaces-dataplane:dataplane {
		uses link-params;
	}
	augment /if:interfaces/interfaces-dataplane:dataplane/interfaces-dataplane:vif/interfaces-dataplane:ip {
		uses link-params;
	}
	augment /if:interfaces/interfaces-loopback:loopback {
		uses link-params;
	}
	augment /if:interfaces/interfaces-switch:switch/interfaces-switch:vif {
		uses link-params;
	}
}
